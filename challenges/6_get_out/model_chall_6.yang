module hidden-module-containing-flag {
    yang-version 1.1;
    namespace "urn:hidden-module:1.0";
  prefix "module-flag";

  contact
    "florian.salaun@nokia.com";

  description
    "Basic model used for a CTF aiming at make people familiar with NETCONF";

  revision "2024-07-11" {
   description "Creation";
  }

  container flag-container
  {
      leaf flag
      {
          config false;
          type string;
          description "The flag";
      }
  }
}
